FEROSNMP-TEST-MIB DEFINITIONS ::= BEGIN

-- Objects served by the test agent (crates/snmp-core/tests/agent/fst_agent.py) for the
-- golden-file query tests. They live under the net-snmp "playpen" arc
-- (1.3.6.1.4.1.8072.9999), which net-snmp reserves for experiments, and
-- cover every SMIv2 base type, enums, units and display hints. The tables
-- below fstTable cover the INDEX codec: a multi-part index (fstPortTable),
-- AUGMENTS (fstPortXTable), an IMPLIED string (fstUserTable) and an enum
-- plus an IMPLIED OBJECT IDENTIFIER (fstPolicyTable). fstSettings can be
-- written, with community "private" or the SNMPv3 user v3-writer.

IMPORTS
    MODULE-IDENTITY, OBJECT-TYPE, Integer32, Unsigned32, Counter32,
    Counter64, Gauge32, TimeTicks, IpAddress, enterprises
        FROM SNMPv2-SMI
    TEXTUAL-CONVENTION, DisplayString, PhysAddress, DateAndTime
        FROM SNMPv2-TC;

ferosnmpTestMIB MODULE-IDENTITY
    LAST-UPDATED "202610290000Z"
    ORGANIZATION "FeroSNMP"
    CONTACT-INFO "https://github.com/jkobierczynski/ferosnmp"
    DESCRIPTION  "Test objects for the FeroSNMP query tests."
    REVISION     "202610290000Z"
    DESCRIPTION  "First version."
    ::= { fstPlaypen 1 }

fstNetSnmp  OBJECT IDENTIFIER ::= { enterprises 8072 }
fstPlaypen  OBJECT IDENTIFIER ::= { fstNetSnmp 9999 }

fstScalars  OBJECT IDENTIFIER ::= { ferosnmpTestMIB 1 }

MacAddress ::= TEXTUAL-CONVENTION
    DISPLAY-HINT "1x:"
    STATUS       current
    DESCRIPTION  "An IEEE 802 MAC address."
    SYNTAX       OCTET STRING (SIZE (6))

Tenths ::= TEXTUAL-CONVENTION
    DISPLAY-HINT "d-1"
    STATUS       current
    DESCRIPTION  "A number in tenths."
    SYNTAX       Integer32

fstString OBJECT-TYPE
    SYNTAX      DisplayString
    MAX-ACCESS  read-only
    STATUS      current
    DESCRIPTION "A printable string."
    ::= { fstScalars 1 }

fstBinary OBJECT-TYPE
    SYNTAX      OCTET STRING
    MAX-ACCESS  read-only
    STATUS      current
    DESCRIPTION "Bytes that are not text."
    ::= { fstScalars 2 }

fstStatus OBJECT-TYPE
    SYNTAX      INTEGER { up(1), down(2), testing(3) }
    MAX-ACCESS  read-only
    STATUS      current
    DESCRIPTION "An enumeration."
    ::= { fstScalars 3 }

fstTemperature OBJECT-TYPE
    SYNTAX      Tenths
    UNITS       "degrees Celsius"
    MAX-ACCESS  read-only
    STATUS      current
    DESCRIPTION "An integer with a display hint and units."
    ::= { fstScalars 4 }

fstOctets OBJECT-TYPE
    SYNTAX      Counter64
    UNITS       "octets"
    MAX-ACCESS  read-only
    STATUS      current
    DESCRIPTION "A 64-bit counter; SNMPv1 cannot carry it."
    ::= { fstScalars 5 }

fstUptime OBJECT-TYPE
    SYNTAX      TimeTicks
    MAX-ACCESS  read-only
    STATUS      current
    DESCRIPTION "Time ticks."
    ::= { fstScalars 6 }

fstAddress OBJECT-TYPE
    SYNTAX      IpAddress
    MAX-ACCESS  read-only
    STATUS      current
    DESCRIPTION "An IPv4 address."
    ::= { fstScalars 7 }

fstPointer OBJECT-TYPE
    SYNTAX      OBJECT IDENTIFIER
    MAX-ACCESS  read-only
    STATUS      current
    DESCRIPTION "An object identifier."
    ::= { fstScalars 8 }

fstMac OBJECT-TYPE
    SYNTAX      PhysAddress
    MAX-ACCESS  read-only
    STATUS      current
    DESCRIPTION "A MAC address (display hint 1x:)."
    ::= { fstScalars 9 }

fstClock OBJECT-TYPE
    SYNTAX      DateAndTime
    MAX-ACCESS  read-only
    STATUS      current
    DESCRIPTION "A date and time (display hint 2d-1d-1d,1d:1d:1d.1d,1a1d:1d)."
    ::= { fstScalars 10 }

fstLevel OBJECT-TYPE
    SYNTAX      Gauge32
    MAX-ACCESS  read-only
    STATUS      current
    DESCRIPTION "A gauge."
    ::= { fstScalars 11 }

fstPackets OBJECT-TYPE
    SYNTAX      Counter32
    MAX-ACCESS  read-only
    STATUS      current
    DESCRIPTION "A 32-bit counter."
    ::= { fstScalars 12 }

fstFlags OBJECT-TYPE
    SYNTAX      BITS { alpha(0), beta(1), gamma(2), delta(9) }
    MAX-ACCESS  read-only
    STATUS      current
    DESCRIPTION "Named bits."
    ::= { fstScalars 13 }

fstSize OBJECT-TYPE
    SYNTAX      Unsigned32
    MAX-ACCESS  read-only
    STATUS      current
    DESCRIPTION "An unsigned number."
    ::= { fstScalars 14 }

fstTable OBJECT-TYPE
    SYNTAX      SEQUENCE OF FstEntry
    MAX-ACCESS  not-accessible
    STATUS      current
    DESCRIPTION "A table with enough rows to need many GETBULK requests."
    ::= { ferosnmpTestMIB 2 }

fstEntry OBJECT-TYPE
    SYNTAX      FstEntry
    MAX-ACCESS  not-accessible
    STATUS      current
    DESCRIPTION "One row."
    INDEX       { fstIndex }
    ::= { fstTable 1 }

FstEntry ::= SEQUENCE {
    fstIndex  Integer32,
    fstName   DisplayString,
    fstCount  Counter32
}

fstIndex OBJECT-TYPE
    SYNTAX      Integer32 (1..2147483647)
    MAX-ACCESS  not-accessible
    STATUS      current
    DESCRIPTION "Row number."
    ::= { fstEntry 1 }

fstName OBJECT-TYPE
    SYNTAX      DisplayString
    MAX-ACCESS  read-only
    STATUS      current
    DESCRIPTION "Row name."
    ::= { fstEntry 2 }

fstCount OBJECT-TYPE
    SYNTAX      Counter32
    MAX-ACCESS  read-only
    STATUS      current
    DESCRIPTION "Row counter."
    ::= { fstEntry 3 }

-- Writable objects, for SET.

fstSettings OBJECT IDENTIFIER ::= { ferosnmpTestMIB 3 }

fstContact OBJECT-TYPE
    SYNTAX      DisplayString (SIZE (0..32))
    MAX-ACCESS  read-write
    STATUS      current
    DESCRIPTION "A string of at most 32 characters."
    ::= { fstSettings 1 }

fstMode OBJECT-TYPE
    SYNTAX      INTEGER { off(1), on(2), auto(3) }
    MAX-ACCESS  read-write
    STATUS      current
    DESCRIPTION "An enumeration."
    ::= { fstSettings 2 }

fstLimit OBJECT-TYPE
    SYNTAX      Integer32 (0..100)
    UNITS       "percent"
    MAX-ACCESS  read-write
    STATUS      current
    DESCRIPTION "An integer with a range."
    ::= { fstSettings 3 }

fstGateway OBJECT-TYPE
    SYNTAX      IpAddress
    MAX-ACCESS  read-write
    STATUS      current
    DESCRIPTION "An IPv4 address."
    ::= { fstSettings 4 }

fstMacAddress OBJECT-TYPE
    SYNTAX      MacAddress
    MAX-ACCESS  read-write
    STATUS      current
    DESCRIPTION "Six bytes, written as 00:1b:21:0a:ff:09."
    ::= { fstSettings 5 }

fstOptions OBJECT-TYPE
    SYNTAX      BITS { alpha(0), beta(1), gamma(2), delta(9) }
    MAX-ACCESS  read-write
    STATUS      current
    DESCRIPTION "Named bits."
    ::= { fstSettings 6 }

fstTarget OBJECT-TYPE
    SYNTAX      OBJECT IDENTIFIER
    MAX-ACCESS  read-write
    STATUS      current
    DESCRIPTION "An object identifier."
    ::= { fstSettings 7 }

fstThreshold OBJECT-TYPE
    SYNTAX      Unsigned32 (1..1000)
    MAX-ACCESS  read-write
    STATUS      current
    DESCRIPTION "An unsigned number with a range."
    ::= { fstSettings 8 }

-- A table with a three-part index: an integer, an IpAddress and a
-- variable-length string, which is encoded with its length.

fstPortTable OBJECT-TYPE
    SYNTAX      SEQUENCE OF FstPortEntry
    MAX-ACCESS  not-accessible
    STATUS      current
    DESCRIPTION "Ports, by slot, address and name."
    ::= { ferosnmpTestMIB 4 }

fstPortEntry OBJECT-TYPE
    SYNTAX      FstPortEntry
    MAX-ACCESS  not-accessible
    STATUS      current
    DESCRIPTION "One port."
    INDEX       { fstPortSlot, fstPortAddress, fstPortName }
    ::= { fstPortTable 1 }

FstPortEntry ::= SEQUENCE {
    fstPortSlot     Integer32,
    fstPortAddress  IpAddress,
    fstPortName     DisplayString,
    fstPortMac      MacAddress,
    fstPortSpeed    Gauge32,
    fstPortStatus   INTEGER
}

fstPortSlot OBJECT-TYPE
    SYNTAX      Integer32 (1..16)
    MAX-ACCESS  not-accessible
    STATUS      current
    DESCRIPTION "Slot number."
    ::= { fstPortEntry 1 }

fstPortAddress OBJECT-TYPE
    SYNTAX      IpAddress
    MAX-ACCESS  not-accessible
    STATUS      current
    DESCRIPTION "Address of the port."
    ::= { fstPortEntry 2 }

fstPortName OBJECT-TYPE
    SYNTAX      DisplayString (SIZE (0..32))
    MAX-ACCESS  not-accessible
    STATUS      current
    DESCRIPTION "Name of the port."
    ::= { fstPortEntry 3 }

fstPortMac OBJECT-TYPE
    SYNTAX      MacAddress
    MAX-ACCESS  read-only
    STATUS      current
    DESCRIPTION "MAC address of the port."
    ::= { fstPortEntry 4 }

fstPortSpeed OBJECT-TYPE
    SYNTAX      Gauge32
    UNITS       "Mbit/s"
    MAX-ACCESS  read-only
    STATUS      current
    DESCRIPTION "Speed."
    ::= { fstPortEntry 5 }

fstPortStatus OBJECT-TYPE
    SYNTAX      INTEGER { up(1), down(2) }
    MAX-ACCESS  read-only
    STATUS      current
    DESCRIPTION "Status."
    ::= { fstPortEntry 6 }

-- Extra columns for fstPortTable, with the same index (AUGMENTS).

fstPortXTable OBJECT-TYPE
    SYNTAX      SEQUENCE OF FstPortXEntry
    MAX-ACCESS  not-accessible
    STATUS      current
    DESCRIPTION "More about each port."
    ::= { ferosnmpTestMIB 5 }

fstPortXEntry OBJECT-TYPE
    SYNTAX      FstPortXEntry
    MAX-ACCESS  not-accessible
    STATUS      current
    DESCRIPTION "More about one port."
    AUGMENTS    { fstPortEntry }
    ::= { fstPortXTable 1 }

FstPortXEntry ::= SEQUENCE {
    fstPortAlias   DisplayString,
    fstPortErrors  Counter32
}

fstPortAlias OBJECT-TYPE
    SYNTAX      DisplayString
    MAX-ACCESS  read-only
    STATUS      current
    DESCRIPTION "Alias."
    ::= { fstPortXEntry 1 }

fstPortErrors OBJECT-TYPE
    SYNTAX      Counter32
    MAX-ACCESS  read-only
    STATUS      current
    DESCRIPTION "Errors."
    ::= { fstPortXEntry 2 }

-- A table indexed by an IMPLIED string, as SNMP-TARGET-MIB and
-- SNMP-VIEW-BASED-ACM-MIB do: no length before the bytes.

fstUserTable OBJECT-TYPE
    SYNTAX      SEQUENCE OF FstUserEntry
    MAX-ACCESS  not-accessible
    STATUS      current
    DESCRIPTION "Users, by name."
    ::= { ferosnmpTestMIB 6 }

fstUserEntry OBJECT-TYPE
    SYNTAX      FstUserEntry
    MAX-ACCESS  not-accessible
    STATUS      current
    DESCRIPTION "One user."
    INDEX       { IMPLIED fstUserName }
    ::= { fstUserTable 1 }

FstUserEntry ::= SEQUENCE {
    fstUserName   DisplayString,
    fstUserGroup  DisplayString,
    fstUserLogins Counter32
}

fstUserName OBJECT-TYPE
    SYNTAX      DisplayString (SIZE (1..32))
    MAX-ACCESS  not-accessible
    STATUS      current
    DESCRIPTION "User name."
    ::= { fstUserEntry 1 }

fstUserGroup OBJECT-TYPE
    SYNTAX      DisplayString
    MAX-ACCESS  read-only
    STATUS      current
    DESCRIPTION "Group."
    ::= { fstUserEntry 2 }

fstUserLogins OBJECT-TYPE
    SYNTAX      Counter32
    MAX-ACCESS  read-only
    STATUS      current
    DESCRIPTION "Logins."
    ::= { fstUserEntry 3 }

-- A table indexed by an enumeration and an IMPLIED OBJECT IDENTIFIER.

fstPolicyTable OBJECT-TYPE
    SYNTAX      SEQUENCE OF FstPolicyEntry
    MAX-ACCESS  not-accessible
    STATUS      current
    DESCRIPTION "Policies, by family and identifier."
    ::= { ferosnmpTestMIB 7 }

fstPolicyEntry OBJECT-TYPE
    SYNTAX      FstPolicyEntry
    MAX-ACCESS  not-accessible
    STATUS      current
    DESCRIPTION "One policy."
    INDEX       { fstPolicyFamily, IMPLIED fstPolicyId }
    ::= { fstPolicyTable 1 }

FstPolicyEntry ::= SEQUENCE {
    fstPolicyFamily  INTEGER,
    fstPolicyId      OBJECT IDENTIFIER,
    fstPolicyHits    Counter64
}

fstPolicyFamily OBJECT-TYPE
    SYNTAX      INTEGER { ipv4(1), ipv6(2) }
    MAX-ACCESS  not-accessible
    STATUS      current
    DESCRIPTION "Address family."
    ::= { fstPolicyEntry 1 }

fstPolicyId OBJECT-TYPE
    SYNTAX      OBJECT IDENTIFIER
    MAX-ACCESS  not-accessible
    STATUS      current
    DESCRIPTION "Policy identifier."
    ::= { fstPolicyEntry 2 }

fstPolicyHits OBJECT-TYPE
    SYNTAX      Counter64
    MAX-ACCESS  read-only
    STATUS      current
    DESCRIPTION "Hits."
    ::= { fstPolicyEntry 3 }

END
